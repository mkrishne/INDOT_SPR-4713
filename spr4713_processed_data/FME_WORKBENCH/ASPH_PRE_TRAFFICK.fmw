FME workspace ASPH_PRE_TRAFFICK.fmw

Parameters:
- DestDataset_ORACLE_NONSPATIAL = spr4713   # Connection
- SourceDataset_CSV2_5 = C:\Users\kmani\purdue.edu\Oscar Moncada - Dr. Shin Shared Folder\spr4713_processed_data\asphalt_pretraffick\processed_asphalt_pre_traffick_data.csv   # Source CSV (Comma Separated Value) File(s)
- SourceDataset_CSV2 = C:\Users\kmani\purdue.edu\Oscar Moncada - Dr. Shin Shared Folder\spr4713_processed_data\asphalt_pretraffick\asphalt_pre_traffick_file_info.csv   # Source CSV (Comma Separated Value) File(s)
- DestDataset_ORACLE_NONSPATIAL_5 = spr4713   # Connection

Readers:
- CSV2_1: CSV2 from $(SourceDataset_CSV2)
- CSV2_3: CSV2 from $(SourceDataset_CSV2_5)

Writers:
- ORACLE_NONSPATIAL_1: ORACLE_NONSPATIAL to $(DestDataset_ORACLE_NONSPATIAL)
- ORACLE_NONSPATIAL_3: ORACLE_NONSPATIAL to $(DestDataset_ORACLE_NONSPATIAL_5)

CSV (reader CSV2_1)
    attributes: Pre Traffick Folder varchar(8), Filename varchar(50), Order of Scan varchar(6), Starting Timestamp datetime, Ending Timestamp datetime, Laser beam offset(mm) real32, Laser beam offset locn varchar(38), Laser beam vertical meas. Low limit(mm) real32, Laser beam vertical meas. High limit(mm) real32, Laser beam vertical meas. range(mm) real32, Carriage Start Position(mm) uint32, Carriage End Position(mm) uint32, Axle Pos. E->W(mm) uint32, Laser Start Position(mm) uint32, Notes varchar(1)
    -> AttributeManager
AttributeManager
    -> ASPH_PRE_TRAFFICK_FILE_INFO (writer ORACLE_NONSPATIAL_1)
ASPH_PRE_TRAFFICK_FILE_INFO (writer ORACLE_NONSPATIAL_1)
    attributes: PRE_TRAFFICK_FOLDER varchar2(10), FILENAME varchar2(100), ORDER_OF_SCAN varchar2(10), STARTING_TIMESTAMP varchar2(20), ENDING_TIMESTAMP varchar2(20), LASER_BEAM_OFFSET_MM float, LASER_BEAM_OFFSET_LOCN varchar2(100), LASER_BEAM_VERTICAL_MEAS_LOW_LIMIT_MM float, LASER_BEAM_VERTICAL_MEAS_HIGH_LIMIT_MM float, LASER_BEAM_VERTICAL_MEAS_RANGE_MM float, CARRIAGE_START_POSITION_MM number(6,0), CARRIAGE_END_POSITION_MM number(6,0), AXLE_POS_E_W_MM number(6,0), LASER_START_POSITION_MM number(6,0), NOTES varchar2(200)
CSV (reader CSV2_3)
    attributes: Filename varchar(49), Sample Number uint32, Horiz(mm)=samp_no*(1384/8088) real64, Laser reading(mm) real64, Laserbeam locn(mm) uint32, Sampled Time time
    -> DatabaseJoiner_2
DatabaseJoiner_2
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.ASPH_PRE_TRAFFICK_FILE_INFO
    JOINED -> AttributeManager_3
AttributeManager_3
    ATTR_TABLE:
      REMOVE Filename
      RENAME_SET_VALUE ID > FILENAME_ID
      REMOVE _matched_records
    -> ASPH_PRE_TRAFFICK_PROCESSED_DATA (writer ORACLE_NONSPATIAL_3)
ASPH_PRE_TRAFFICK_PROCESSED_DATA (writer ORACLE_NONSPATIAL_3)
    attributes: SAMPLE_NUMBER number(10,0), HORIZ_MM_SAMP_NO_1384_8088 float, LASER_READING float, LASERBEAM_LOCN_MM number(10,0), SAMPLED_TIME timestamp, FILENAME_ID varchar2(200), Q__MATCHED_RECORDS number(10,0)
