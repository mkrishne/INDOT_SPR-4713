FME workspace ASPH_SENSOR.fmw

Parameters:
- DestDataset_ORACLE_NONSPATIAL = spr4713   # Connection
- SourceDataset_CSV2_9 = C:\Users\kmani\purdue.edu\Oscar Moncada - Dr. Shin Shared Folder\spr4713_processed_data\asphalt_sensor\asphalt_asg_processed_csv_data.csv   # Source CSV (Comma Separated Value) File(s)
- SourceDataset_CSV2 = C:\Users\kmani\purdue.edu\Oscar Moncada - Dr. Shin Shared Folder\spr4713_processed_data\asphalt_sensor\asphalt_sensor_file_info.csv   # Source CSV (Comma Separated Value) File(s)
- DestDataset_ORACLE_NONSPATIAL_9 = spr4713   # Connection
- SourceDataset_CSV2_7 = C:\Users\kmani\purdue.edu\Oscar Moncada - Dr. Shin Shared Folder\spr4713_processed_data\asphalt_sensor\asphalt_csg_processed_csv_data.csv   # Source CSV (Comma Separated Value) File(s)
- DestDataset_ORACLE_NONSPATIAL_7 = spr4713   # Connection
- SourceDataset_CSV2_6 = C:\Users\kmani\purdue.edu\Oscar Moncada - Dr. Shin Shared Folder\spr4713_processed_data\asphalt_sensor\asphalt_pc_processed_csv_data.csv   # Source CSV (Comma Separated Value) File(s)
- DestDataset_ORACLE_NONSPATIAL_6 = spr4713   # Connection
- SourceDataset_CSV2_8 = C:\Users\kmani\purdue.edu\Oscar Moncada - Dr. Shin Shared Folder\spr4713_processed_data\asphalt_sensor\asphalt_thermo_processed_csv_data.csv   # Source CSV (Comma Separated Value) File(s)
- DestDataset_ORACLE_NONSPATIAL_8 = spr4713   # Connection

Readers:
- CSV2_1: CSV2 from $(SourceDataset_CSV2)
- CSV2_2: CSV2 from $(SourceDataset_CSV2_9)
- CSV2_3: CSV2 from $(SourceDataset_CSV2_7)
- CSV2_4: CSV2 from $(SourceDataset_CSV2_6)
- CSV2_5: CSV2 from $(SourceDataset_CSV2_8)

Writers:
- ORACLE_NONSPATIAL_1: ORACLE_NONSPATIAL to $(DestDataset_ORACLE_NONSPATIAL)
- ORACLE_NONSPATIAL_2: ORACLE_NONSPATIAL to $(DestDataset_ORACLE_NONSPATIAL_9)
- ORACLE_NONSPATIAL_3: ORACLE_NONSPATIAL to $(DestDataset_ORACLE_NONSPATIAL_7)
- ORACLE_NONSPATIAL_4: ORACLE_NONSPATIAL to $(DestDataset_ORACLE_NONSPATIAL_6)
- ORACLE_NONSPATIAL_5: ORACLE_NONSPATIAL to $(DestDataset_ORACLE_NONSPATIAL_8)

CSV (reader CSV2_2)
    attributes: Filename varchar(28), Captured instance varchar(8), Asphalt Strain Gage uint32, Placement uint32, Cal Coeff(x10-6/1x10-6) real32, Rated Output(x10-6) uint32, Extrema varchar(7), SecondsElapsed real32, processed_datapoint(microstrain) real64
    -> DatabaseJoiner
DatabaseJoiner
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.ASPH_SENSOR_FILE_INFO
    JOINED -> AttributeManager_2
AttributeManager_2
    ATTR_TABLE:
      REMOVE Filename
      RENAME_SET_VALUE ID > FILENAME_ID
      REMOVE _matched_records
    -> ASPH_ASG_PROCESSED_DATA (writer ORACLE_NONSPATIAL_2)
ASPH_ASG_PROCESSED_DATA (writer ORACLE_NONSPATIAL_2)
    attributes: CAPTURED_INSTANCE varchar2(20), ASG_NO number(3,0), PLACEMENT number(3,0), CAL_COEFF float, RATED_OUTPUT number(6,0), EXTREMA varchar2(7), SECONDS_ELAPSED float, PROCESSED_DATAPOINT_MICROSTRAIN float, FILENAME_ID number
CSV (reader CSV2_3)
    attributes: Filename varchar(28), Captured instance varchar(8), Concrete Strain Gage uint32, Placement uint32, Lin Gage Fctr(inches/mV/V) real32, Poly Gage Fctr A real64, Poly Gage Fctr B real32, Extrema varchar(7), SecondsElapsed real32, processed_datapoint(inches) real64
    -> DatabaseJoiner_2
DatabaseJoiner_2
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.ASPH_SENSOR_FILE_INFO
    JOINED -> AttributeManager_3
AttributeManager_3
    ATTR_TABLE:
      REMOVE Filename
      REMOVE _matched_records
    -> ASPH_CSG_PROCESSED_DATA (writer ORACLE_NONSPATIAL_3)
ASPH_CSG_PROCESSED_DATA (writer ORACLE_NONSPATIAL_3)
    attributes: FILENAME_ID number, CAPTURED_INSTANCE varchar2(20), CSG_NO number(3,0), PLACEMENT number(3,0), LIN_GAGE_FCTR float, POLY_GAGE_FCTR_A float, POLY_GAGE_FCTR_B float, EXTREMA varchar2(7), SECONDS_ELAPSED float, PROCESSED_DATAPOINT_INCHES float
CSV (reader CSV2_1)
    attributes: Filename varchar(29), Day uint32, Date date, Operator varchar(15), Number of passes uint32, Cummulative Number of Passes uint32, Room Temp (F) uint32, Pavement Temp  (F) uint32, Input Axel Load real32, Measured Axel Load (lb) real32, Plug-in Axel Load (kips) real32, Run Number real32, Notes varchar(108)
    -> AttributeManager
AttributeManager
    -> ASPH_SENSOR_FILE_INFO (writer ORACLE_NONSPATIAL_1)
ASPH_SENSOR_FILE_INFO (writer ORACLE_NONSPATIAL_1)
    attributes: FILENAME varchar2(100), DAY_NO number(6,0), DATE_OF_COLLECTION date, OPERATOR varchar2(30), NUMBER_OF_PASSES number(6,0), CUMULATIVE_NUMBER_OF_PASSES number(10,0), ROOM_TEMP_F number(4,0), PAVEMENT_TEMP_F number(4,0), INPUT_AXEL_LOAD number(6,0), MEASURED_AXEL_LOAD_LB number(6,0), PLUG_IN_AXEL_LOAD_KIPS float, RUN_NUMBER number(5,0), NOTES varchar2(200)
CSV (reader CSV2_4)
    attributes: Filename varchar(29), Captured instance varchar(8), Pressure Cell real32, Lin Gage Fctr(kPa/mV) real32, Poly Gage Fctr A real64, Poly Gage Fctr B real32, Poly Gage Fctr C real32, Extrema varchar(7), SecondsElapsed real32, processed_datapoint(kPa) real64
    -> DatabaseJoiner_3
DatabaseJoiner_3
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.ASPH_SENSOR_FILE_INFO
    JOINED -> AttributeManager_4
AttributeManager_4
    ATTR_TABLE:
      REMOVE Filename
      REMOVE _matched_records
    -> ASPH_PC_PROCESSED_DATA (writer ORACLE_NONSPATIAL_4)
ASPH_PC_PROCESSED_DATA (writer ORACLE_NONSPATIAL_4)
    attributes: FILENAME_ID number, CAPTURED_INSTANCE varchar2(20), PC_NO float, LIN_GAGE_FCTR float, POLY_GAGE_FCTR_A float, POLY_GAGE_FCTR_B float, POLY_GAGE_FCTR_C float, EXTREMA varchar2(7), SECONDS_ELAPSED float, PROCESSED_DATAPOINT_KPA float
CSV (reader CSV2_5)
    attributes: Filename varchar(29), Captured instance varchar(8), Thermocouple real32, Extrema varchar(7), SecondsElapsed real32, processed_datapoint(F) real64
    -> DatabaseJoiner_4
DatabaseJoiner_4
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.ASPH_SENSOR_FILE_INFO
    JOINED -> AttributeManager_5
AttributeManager_5
    ATTR_TABLE:
      REMOVE Filename
      REMOVE _matched_records
    -> ASPH_THERMO_PROCESSED_DATA (writer ORACLE_NONSPATIAL_5)
ASPH_THERMO_PROCESSED_DATA (writer ORACLE_NONSPATIAL_5)
    attributes: FILENAME_ID number, CAPTURED_INSTANCE varchar2(20), THERMOCOUPLE_NO number(3,0), EXTREMA varchar2(7), SECONDS_ELAPSED float, PROCESSED_DATAPOINT_F float
