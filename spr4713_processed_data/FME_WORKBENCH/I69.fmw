FME workspace I69.fmw

Parameters:
- DestDataset_ORACLE_NONSPATIAL_6 = spr4713   # Connection
- DestDataset_ORACLE_NONSPATIAL = spr4713   # Connection
- SourceDataset_CSV2_3 = C:\Users\kmani\OneDrive\Desktop\INDOT\App_Final\App_Final\Database\processed_data2.csv   # Source CSV (Comma Separated Value) File(s)

Readers:
- CSV2_2: CSV2 from $(SourceDataset_CSV2_3)

Writers:
- ORACLE_NONSPATIAL_1: ORACLE_NONSPATIAL to $(DestDataset_ORACLE_NONSPATIAL)
- ORACLE_NONSPATIAL_2: ORACLE_NONSPATIAL to $(DestDataset_ORACLE_NONSPATIAL_6)

CSV (reader CSV2_2)
    attributes: Project_Name varchar(5), Test_Section uint32, Sensor_Type varchar(14), Location real32, GageID uint32, date varchar(10), Description varchar(5), Filename varchar(45), cal_factor real32, b_value real32, x x_coordinate, y y_coordinate, Extrema varchar(7), load_lb uint32
    -> UniqueValueLogger
    -> DatabaseJoiner
UniqueValueLogger
    VAL = @Value(Filename)
    -> DatabaseJoiner_2
DatabaseJoiner_2
    ADDED_FIELDS = FILENAME
    ATTR_ACCUM_MODE = Merge Joined
    ATTR_CONFLICT_RES = Use Original
    CACHE_SIZE = 5000
    DATASET = spr4713
    FORMAT = ORACLE_NONSPATIAL
    JOIN_KEYS = _value FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.I69_FILE_INFO
    UNJOINED -> AttributeManager_2
AttributeManager_2
    ATTR_TABLE = RENAME_SET_VALUE _value > FILENAME
    -> I69_FILE_INFO (writer ORACLE_NONSPATIAL_1)
I69_FILE_INFO (writer ORACLE_NONSPATIAL_1)
    attributes: Q__COUNT number(10,0), Q__VALUE varchar2(200), FILENAME varchar2(200), ID varchar2(200), Q__MATCHED_RECORDS number(10,0)
DatabaseJoiner
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.I69_FILE_INFO
    JOINED -> AttributeManager
AttributeManager
    ATTR_TABLE:
      REMOVE Filename
      RENAME_SET_VALUE ID > FILENAME_ID
      REMOVE _matched_records
    -> I69_PROCESSED_DATA (writer ORACLE_NONSPATIAL_2)
I69_PROCESSED_DATA (writer ORACLE_NONSPATIAL_2)
    attributes: PROJECT_NAME varchar2(10), TEST_SECTION number(5,0), SENSOR_TYPE varchar2(14), LOCATION number(5,2), GAGEID number(6,0), SURVEY_DATE varchar2(10), DESCRIPTION varchar2(5), CAL_FACTOR number(8,4), B_VALUE number(7,5), X number(8,5), Y number(12,5), LOAD_LB number(5,0), FILENAME_ID number, EXTREMA varchar2(8)

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
