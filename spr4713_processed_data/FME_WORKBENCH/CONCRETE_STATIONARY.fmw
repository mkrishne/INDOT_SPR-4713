FME workspace CONCRETE_STATIONARY.fmw

Parameters:
- SourceDataset_CSV2 = C:\Users\kmani\purdue.edu\Oscar Moncada - Dr. Shin Shared Folder\spr4713_processed_data\concrete_stationary\concrete_static_sensor_file_info.csv   # Source CSV (Comma Separated Value) File(s)
- DestDataset_ORACLE_NONSPATIAL = spr4713   # Connection
- SourceDataset_CSV2_5 = C:\Users\kmani\purdue.edu\Oscar Moncada - Dr. Shin Shared Folder\spr4713_processed_data\concrete_stationary\concrete_static_csg_processed_csv_data.csv   # Source CSV (Comma Separated Value) File(s)
- DestDataset_ORACLE_NONSPATIAL_5 = spr4713   # Connection
- SourceDataset_CSV2_7 = C:\Users\kmani\purdue.edu\Oscar Moncada - Dr. Shin Shared Folder\spr4713_processed_data\concrete_stationary\concrete_static_pc_processed_csv_data.csv   # Source CSV (Comma Separated Value) File(s)
- DestDataset_ORACLE_NONSPATIAL_7 = spr4713   # Connection
- SourceDataset_CSV2_6 = C:\Users\kmani\purdue.edu\Oscar Moncada - Dr. Shin Shared Folder\spr4713_processed_data\concrete_stationary\concrete_static_thermo_processed_csv_data.csv   # Source CSV (Comma Separated Value) File(s)
- DestDataset_ORACLE_NONSPATIAL_6 = spr4713   # Connection

Readers:
- CSV2_1: CSV2 from $(SourceDataset_CSV2)
- CSV2_2: CSV2 from $(SourceDataset_CSV2_5)
- CSV2_3: CSV2 from $(SourceDataset_CSV2_7)
- CSV2_4: CSV2 from $(SourceDataset_CSV2_6)

Writers:
- ORACLE_NONSPATIAL_1: ORACLE_NONSPATIAL to $(DestDataset_ORACLE_NONSPATIAL)
- ORACLE_NONSPATIAL_2: ORACLE_NONSPATIAL to $(DestDataset_ORACLE_NONSPATIAL_5)
- ORACLE_NONSPATIAL_3: ORACLE_NONSPATIAL to $(DestDataset_ORACLE_NONSPATIAL_7)
- ORACLE_NONSPATIAL_4: ORACLE_NONSPATIAL to $(DestDataset_ORACLE_NONSPATIAL_6)

CSV (reader CSV2_2)
    attributes: Filename varchar(13), Concrete Strain Gage uint32, Placement uint32, Lin Gage Fctr(inches/mV/V) real32, Poly Gage Fctr A real64, Poly Gage Fctr B real32, Extrema varchar(7), SecondsElapsed real32, processed_datapoint(inches) real64
    -> DatabaseJoiner
DatabaseJoiner
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.CONCRETE_STATIC_SENSOR_FILE_INFO
    JOINED -> AttributeManager_2
AttributeManager_2
    ATTR_TABLE:
      REMOVE Filename
      RENAME_SET_VALUE ID > FILENAME_ID
      REMOVE _matched_records
    -> CONCRETE_STATIC_CSG_PROCESSED_DATA (writer ORACLE_NONSPATIAL_2)
CONCRETE_STATIC_CSG_PROCESSED_DATA (writer ORACLE_NONSPATIAL_2)
    attributes: FILENAME_ID number, CSG_NO number(3,0), PLACEMENT number(3,0), LIN_GAGE_FCTR float, POLY_GAGE_FCTR_A float, POLY_GAGE_FCTR_B float, EXTREMA varchar2(7), SECONDS_ELAPSED float, PROCESSED_DATAPOINT_INCHES float
CSV (reader CSV2_1)
    attributes: Filename varchar(14), Scan Point varchar(10), Starting Timestamp datetime
    -> AttributeManager
AttributeManager
    -> CONCRETE_STATIC_SENSOR_FILE_INFO (writer ORACLE_NONSPATIAL_1)
CONCRETE_STATIC_SENSOR_FILE_INFO (writer ORACLE_NONSPATIAL_1)
    attributes: FILENAME varchar2(100), SCAN_POINT varchar2(20), STARTING_TIMESTAMP timestamp
CSV (reader CSV2_3)
    attributes: Filename varchar(13), Pressure Cell uint32, Lin Gage Fctr(kPa/mV) real32, Poly Gage Fctr A real32, Poly Gage Fctr B real32, Poly Gage Fctr C real32, Extrema varchar(7), SecondsElapsed real32, processed_datapoint(kPa) real64
    -> DatabaseJoiner_2
DatabaseJoiner_2
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.CONCRETE_STATIC_SENSOR_FILE_INFO
    JOINED -> AttributeManager_3
AttributeManager_3
    ATTR_TABLE:
      REMOVE Filename
      REMOVE _matched_records
    -> CONCRETE_STATIC_PC_PROCESSED_DATA (writer ORACLE_NONSPATIAL_3)
CONCRETE_STATIC_PC_PROCESSED_DATA (writer ORACLE_NONSPATIAL_3)
    attributes: FILENAME_ID number, PC_NO number(3,0), LIN_GAGE_FCTR float, POLY_GAGE_FCTR_A float, POLY_GAGE_FCTR_B float, POLY_GAGE_FCTR_C float, EXTREMA varchar2(7), SECONDS_ELAPSED float, PROCESSED_DATAPOINT_KPA float
CSV (reader CSV2_4)
    attributes: Filename varchar(14), Thermocouple uint32, Extrema varchar(7), SecondsElapsed real32, processed_datapoint(F) real64
    -> DatabaseJoiner_3
DatabaseJoiner_3
    ADDED_FIELDS = ID
    ATTR_ACCUM_MODE = Merge Joined
    ATTR_CONFLICT_RES = Use Original
    CACHE_SIZE = 5000
    DATASET = spr4713
    FORMAT = ORACLE_NONSPATIAL
    JOIN_KEYS = Filename FILENAME
    MATCH_MULTIPLE_DISPLAY = Create a feature for each match
    MATCH_RULE_DISPLAY = Match All (1:M)
    ORACLE_NONSPATIAL_CREATE_FEATURE_TABLES_FROM_DATA = Yes
    ORACLE_NONSPATIAL_NAMED_CONNECTION = spr4713
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    PREFETCH_EXHAUSTIVE = Yes
    TABLE = C##SPR4713.CONCRETE_STATIC_SENSOR_FILE_INFO
    JOINED -> AttributeManager_4
AttributeManager_4
    ATTR_TABLE:
      REMOVE Filename
      RENAME_SET_VALUE ID > FILENAME_ID
      REMOVE _matched_records
    -> CONCRETE_STATIC_THERMO_PROCESSED_DATA (writer ORACLE_NONSPATIAL_4)
CONCRETE_STATIC_THERMO_PROCESSED_DATA (writer ORACLE_NONSPATIAL_4)
    attributes: FILENAME_ID number, THERMO_NO number(3,0), EXTREMA varchar2(7), SECONDS_ELAPSED float, PROCESSED_DATAPOINT_F float
